# Synthetic Schema-Coverage DOORS Export

# Specification: Module One

## 1: Rendering Score
The system shall render a weighted score. See steps below:
1. collect inputs
2. weight them
| Summary (merged) |  |
| --- | --- |
| Weight | 0.8 |
See also external spec section 3.
- Category: Safety, Performance
- Score: 0.875
- Satisfies -> 2
- Satisfies -> 1

## 2: Sparse Attribute Case
The system shall still import correctly when a defined attribute has no value on this particular item.
- Category: Safety
- Derives -> 1

# Specification: Module Two (empty)
