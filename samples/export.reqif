# Synthetic DOORS Export

# Specification: System Requirements

## 1: User Authentication
The system shall authenticate users before granting access to any protected resource.
- ASIL: B

## 2: Account Lockout
The system shall lock an account after five consecutive failed authentication attempts.
- ASIL: B
- Link -> 1

## 3: Authentication Logging
The system shall log every authentication attempt with timestamp and outcome.
- ASIL: A
- Link -> 1

## 4: Session Timeout
The system shall terminate an idle session after fifteen minutes.
- ASIL: QM

## 5: Password Complexity
The system shall reject passwords shorter than twelve characters.
- ASIL: A
