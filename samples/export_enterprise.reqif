# Synthetic Enterprise DOORS Export

# Specification: Enterprise System Requirements

## so-HEAD-1: 1. Bezpečnosť (Security) (Heading)

### 10: Overenie identity (Requirement)
Systém musí overiť identitu užívateľa pred udelením prístupu k chránenému zdroju.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
- ASIL: B
- Priority: High
- Suspect: false
- LastReviewed: 2026-10-15T00:00:00.000+02:00

### 11: Uzamknutie účtu (Requirement)
Systém musí uzamknúť účet po piatich neúspešných pokusoch o prihlásenie.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
- ASIL: B
- Priority: Medium
- Suspect: true
- LastReviewed: 2026-09-01T00:00:00.000+02:00
- Link -> 10

### 12: Záznam udalostí (Requirement)
Systém musí zaznamenať každý pokus o overenie s časovou pečiatkou a výsledkom. Príloha: [schéma architektúry]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
- ASIL: A
- Priority: Low
- Suspect: false
- LastReviewed: 2026-10-15T00:00:00.000+02:00
- Link -> 10

## so-HEAD-2: 2. Prevádzka (Operations) (Heading)

### 20: Časový limit relácie (Requirement)
Systém musí ukončiť nečinnú relácie po pätnástich minútach.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
- ASIL: QM
- Priority: Low
- Suspect: false
- LastReviewed: 2026-08-01T00:00:00.000+02:00
